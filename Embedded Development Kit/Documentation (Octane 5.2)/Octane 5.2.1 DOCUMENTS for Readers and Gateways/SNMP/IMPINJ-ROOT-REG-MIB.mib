-- *************************************************************
-- *
-- * IMPINJ-ROOT-REG-MIB.mib: The Impinj Root Registration MIB
-- *
-- * DESCRIPTION: This MIB describes the top-level Impinj Root
-- *              Registration MIB. All subsequent Impinj MIBs 
-- *              must import this MIB to resolve its location
-- *              in the "impinj" enterprises branch.
-- *
-- * Copyright (c) 2006, 2009, 2010, 2011 Impinj, Inc.
-- * All Rights Reserved - Licensed Software
-- * 
-- *************************************************************

IMPINJ-ROOT-REG-MIB DEFINITIONS ::= BEGIN

IMPORTS
   MODULE-IDENTITY, OBJECT-IDENTITY, enterprises
      FROM SNMPv2-SMI;

--
-- The Impinj administratively maintained name space starts here.
--
-- The enterprise ID assigned to Impinj by the IANA: 25882.
--

impinj  MODULE-IDENTITY
   LAST-UPDATED 
      "201104181500Z"   -- April 18, 2011 15:00
   ORGANIZATION
      "Impinj, Inc."
   CONTACT-INFO
      "Impinj, Inc.
       701 North 34th Street
       Suite 300
       Seattle, WA 98103 USA
       Phone: +1 206-517-5300
       Fax: +1 206-517-5262
       Email: support@impinj.com" 
   DESCRIPTION
      "This MIB module contains MIB variables that define the
       structure of the Impinj, Inc. enterprise name space. It
       defines the top-level enterprise node." 
   REVISION
      "201104181500Z"   -- April 18, 2011 15:00
   DESCRIPTION
      "Initial version of this MIB module." 
   ::= { enterprises 25882 }

-- ***************************************************************
-- 
-- Definitions for the top level of the Impinj OID name space
--
-- ***************************************************************

impRegistration  OBJECT-IDENTITY
   STATUS current
   DESCRIPTION
      "Root for registration for Impinj Modules."
   ::= { impinj 1 }

impProduct  OBJECT-IDENTITY      
   STATUS current
   DESCRIPTION
      "Root for definition of Impinj product-specific object IDs."
   ::= { impinj 2 }

impExperimental  OBJECT-IDENTITY 
   STATUS current
   DESCRIPTION
      "Root for definition of experimental Impinj enterprise MIBs."
   ::= { impinj 3 }

-- ***************************************************************
-- 
-- REGISTRATION: objects that provide further partitioning for 
--               specific modules
--
-- ***************************************************************

impModules  OBJECT-IDENTITY 
   STATUS current
   DESCRIPTION
      "Root registration for Impinj MIB MODULE-IDENTITY objects."
   ::= { impRegistration 1 }

impReader  OBJECT-IDENTITY  
   STATUS current
   DESCRIPTION
      "Root for definition of Impinj RFID Reader products."
   ::= { impProduct 1 }

-- ***************************************************************
-- 
-- PRODUCT: objects that provide further partitioning for the Impinj
--          Reader product types
--
-- ***************************************************************

impSpeedway  OBJECT-IDENTITY
   STATUS current
   DESCRIPTION
      "OID definition for Impinj Speedway Reader. This is used for the
       sysObjectID value (1.3.6.1.4.1.25882.2.1.1) within the managed
       device."
   ::= { impReader 1 }

impSpeedwayRevolution  OBJECT-IDENTITY
   STATUS current
   DESCRIPTION
      "OID definition for Impinj SpeedwayRevolution Reader. This is used for
       the sysObjectID value (1.3.6.1.4.1.25882.2.1.2) within the managed
       device."
   ::= { impReader 2 }

impSpeedwayWirelessLan  OBJECT-IDENTITY
   STATUS current
   DESCRIPTION
      "OID definition for Impinj Speedway Reader with wireless networking.
       This is used for the sysObjectID value (1.3.6.1.4.1.25882.2.1.3)
       within the managed device."
   ::= { impReader 3 }

impMicroneticsRFIDForkliftSystem  OBJECT-IDENTITY
   STATUS current
   DESCRIPTION
      "OID definition for Micronetics RFID Forklift System powered by Impinj.
       This is used for the sysObjectID value (1.3.6.1.4.1.25882.2.1.4)
       within the managed device."
   ::= { impReader 4 }

-- ***************************************************************
-- 
-- PRODUCT: objects that provide further partitioning for the Impinj
--          Reader product types
--
-- ***************************************************************

impSpeedwayR1000 OBJECT-IDENTITY
   STATUS current
   DESCRIPTION
      "OID definition for Impinj Speedway R1000 Reader. This is used
       for the sysObjectID value (1.3.6.1.4.1.25882.2.1.1.1) within the managed
       device."
   ::= { impSpeedway 1 }

-- ***************************************************************
-- 
-- PRODUCT: objects that provide further partitioning for the Impinj
--          Revolution Reader product types
--
-- ***************************************************************

impSpeedwayRevR220  OBJECT-IDENTITY
   STATUS current
   DESCRIPTION
      "OID definition for Impinj Speedway Revolution R220 Reader. This is used
       for the sysObjectID value (1.3.6.1.4.1.25882.2.1.2.1) within the managed
       device."
   ::= { impSpeedwayRevolution 1 }

impSpeedwayRevR420  OBJECT-IDENTITY
   STATUS current
   DESCRIPTION
      "OID definition for Impinj Speedway Revolution R420 Reader. This is used
       for the sysObjectID value (1.3.6.1.4.1.25882.2.1.2.2) within the managed
       device."
   ::= { impSpeedwayRevolution 2 }

impSpeedwayRevR660  OBJECT-IDENTITY
   STATUS current
   DESCRIPTION
      "OID definition for Impinj xArray Reader. This is used
       for the sysObjectID value (1.3.6.1.4.1.25882.2.1.2.3) within the managed
       device."
   ::= { impSpeedwayRevolution 3 }

impSpeedwayRevR680  OBJECT-IDENTITY
   STATUS current
   DESCRIPTION
      "OID definition for Impinj xArray Reader. This is used
       for the sysObjectID value (1.3.6.1.4.1.25882.2.1.2.7) within the managed
       device."
   ::= { impSpeedwayRevolution 7 }


-- ***************************************************************
-- 
-- PRODUCT: objects that provide partitioning for the Impinj
--          Speedway R1000 based on region
--
-- ***************************************************************

impSpeedwayR1000Fcc OBJECT-IDENTITY
   STATUS current
   DESCRIPTION
      "OID definition for Impinj Speedway R1000 Reader in the FCC
       region. This is used for the sysObjectID value
       (1.3.6.1.4.1.25882.2.1.1.1.1000) within the managed device."
   ::= { impSpeedwayR1000 1000 }
   
impSpeedwayR1000ETSI300-220 OBJECT-IDENTITY
   STATUS current
   DESCRIPTION
      "OID definition for Impinj Speedway R1000 Reader in the 
	   ETSI EN 300-220 region. This is used for the sysObjectID value
       (1.3.6.1.4.1.25882.2.1.1.1.1001) within the managed device."
   ::= { impSpeedwayR1000 1001 }

impSpeedwayR1000ETSI302-208 OBJECT-IDENTITY
   STATUS current
   DESCRIPTION
      "OID definition for Impinj Speedway R1000 Reader in the 
	   ETSI EN 302-208 region. This is used for the sysObjectID value
       (1.3.6.1.4.1.25882.2.1.1.1.1002) within the managed device."
   ::= { impSpeedwayR1000 1002 }
   
impSpeedwayR1000HongKong OBJECT-IDENTITY
   STATUS current
   DESCRIPTION
      "OID definition for Impinj Speedway R1000 Reader in the Hong
       Kong region. This is used for the sysObjectID value
       (1.3.6.1.4.1.25882.2.1.1.1.1003) within the managed device."
   ::= { impSpeedwayR1000 1003 }

impSpeedwayR1000Taiwan OBJECT-IDENTITY
   STATUS current
   DESCRIPTION
      "OID definition for Impinj Speedway R1000 Reader in the Taiwan
       region. This is used for the sysObjectID value
       (1.3.6.1.4.1.25882.2.1.1.1.1004) within the managed device."
   ::= { impSpeedwayR1000 1004 }

impSpeedwayR1000Japan OBJECT-IDENTITY
   STATUS current
   DESCRIPTION
      "OID definition for Impinj Speedway R1000 Reader in the Japan 
       952-954 region. This is used for the sysObjectID
       value (1.3.6.1.4.1.25882.2.1.1.1.1005) within the managed device."
   ::= { impSpeedwayR1000 1005 }

impSpeedwayR1000JapanLowPower OBJECT-IDENTITY
   STATUS current
   DESCRIPTION
      "OID definition for Impinj Speedway R1000 Reader in the Japan 
       952-954 region using low power (<10mW). This is used for the sysObjectID
       value (1.3.6.1.4.1.25882.2.1.1.1.1006) within the managed device."
   ::= { impSpeedwayR1000 1006 }

impSpeedwayR1000ETSI302-208-ver1-2-1 OBJECT-IDENTITY
   STATUS current
   DESCRIPTION
      "OID definition for Impinj Speedway R1000 Reader in the ETSI
       region (Reg 302.208 ver 1.2.1). This is used for the sysObjectID
       value (1.3.6.1.4.1.25882.2.1.1.1.1007) within the managed device."
   ::= { impSpeedwayR1000 1007 }

impSpeedwayR1000Korea OBJECT-IDENTITY
   STATUS current
   DESCRIPTION
      "OID definition for Impinj Speedway R1000 Reader in the Korea region.
       This is used for the sysObjectID value (1.3.6.1.4.1.25882.2.1.1.1.1008)
       within the managed device."
   ::= { impSpeedwayR1000 1008 }

impSpeedwayR1000Malaysia OBJECT-IDENTITY
   STATUS current
   DESCRIPTION
      "OID definition for Impinj Speedway R1000 Reader in the Malaysia region.
       This is used for the sysObjectID value (1.3.6.1.4.1.25882.2.1.1.1.1009)
       within the managed device."
   ::= { impSpeedwayR1000 1009 }

impSpeedwayR1000China OBJECT-IDENTITY
   STATUS current
   DESCRIPTION
      "OID definition for Impinj Speedway R1000 Reader in the China region.
       This is used for the sysObjectID value (1.3.6.1.4.1.25882.2.1.1.1.1010)
       within the managed device."
   ::= { impSpeedwayR1000 1010 }

impSpeedwayR1000JapanNoLBT OBJECT-IDENTITY
   STATUS current
   DESCRIPTION
      "OID definition for Impinj Speedway R1000 Reader in the Japan 952-954 
	   region without LBT. This is used for the sysObjectID value 
	   (1.3.6.1.4.1.25882.2.1.1.1.1011) within the managed device."
   ::= { impSpeedwayR1000 1011 }

impSpeedwayR1000SouthAfrica OBJECT-IDENTITY
   STATUS current
   DESCRIPTION
      "OID definition for Impinj Speedway R1000 Reader in the South Africa region.
       This is used for the sysObjectID value (1.3.6.1.4.1.25882.2.1.1.1.1012)
       within the managed device."
   ::= { impSpeedwayR1000 1012 }

impSpeedwayR1000Brazil OBJECT-IDENTITY
   STATUS current
   DESCRIPTION
      "OID definition for Impinj Speedway R1000 Reader in the
       Brazil region. This is used for the sysObjectID value
       (1.3.6.1.4.1.25882.2.1.1.1.1013) within the managed device."
   ::= { impSpeedwayR1000 1013 }

impSpeedwayR1000Thailand OBJECT-IDENTITY
   STATUS current
   DESCRIPTION
      "OID definition for Impinj Speedway R1000 Reader in the
       Thailand region. This is used for the sysObjectID value
       (1.3.6.1.4.1.25882.2.1.1.1.1014) within the managed device."
   ::= { impSpeedwayR1000 1014 }

impSpeedwayR1000Singapore OBJECT-IDENTITY
   STATUS current
   DESCRIPTION
      "OID definition for Impinj Speedway R1000 Reader in the
       Singapore region. This is used for the sysObjectID value
       (1.3.6.1.4.1.25882.2.1.1.1.1015) within the managed device."
   ::= { impSpeedwayR1000 1015 }

impSpeedwayR1000Australia OBJECT-IDENTITY
   STATUS current
   DESCRIPTION
      "OID definition for Impinj Speedway R1000 Reader in the
       Australia region. This is used for the sysObjectID value
       (1.3.6.1.4.1.25882.2.1.1.1.1016) within the managed device."
   ::= { impSpeedwayR1000 1016 }

impSpeedwayR1000India OBJECT-IDENTITY
   STATUS current
   DESCRIPTION
      "OID definition for Impinj Speedway R1000 R220 Reader in the
       India region. This is used for the sysObjectID value
       (1.3.6.1.4.1.25882.2.1.1.1.1017) within the managed device."
   ::= { impSpeedwayR1000 1017 }

impSpeedwayR1000Uruguay OBJECT-IDENTITY
   STATUS current
   DESCRIPTION
      "OID definition for Impinj Speedway R1000 Reader in the
       Uruguay region. This is used for the sysObjectID value
       (1.3.6.1.4.1.25882.2.1.1.1.1018) within the managed device."
   ::= { impSpeedwayR1000 1018 }

impSpeedwayR1000Vietnam OBJECT-IDENTITY
   STATUS current
   DESCRIPTION
      "OID definition for Impinj Speedway R1000 Reader in the
       Vietnam region. This is used for the sysObjectID value
       (1.3.6.1.4.1.25882.2.1.1.1.1019) within the managed device."
   ::= { impSpeedwayR1000 1019 }

impSpeedwayR1000Israel OBJECT-IDENTITY
   STATUS current
   DESCRIPTION
      "OID definition for Impinj Speedway R1000 Reader in the
       Israel region. This is used for the sysObjectID value
       (1.3.6.1.4.1.25882.2.1.1.1.1.1020) within the managed device."
   ::= { impSpeedwayR1000 1020 }

impSpeedwayR1000Philippines OBJECT-IDENTITY
   STATUS current
   DESCRIPTION
      "OID definition for Impinj Speedway R1000 Reader in the
       Philippines region. This is used for the sysObjectID value
       (1.3.6.1.4.1.25882.2.1.1.1.1.1021) within the managed device."
   ::= { impSpeedwayR1000 1021 }

impSpeedwayR1000CanadaPost OBJECT-IDENTITY
   STATUS current
   DESCRIPTION
      "OID definition for Impinj Speedway R1000 Reader in the
       CanadaPost region. This is used for the sysObjectID value
       (1.3.6.1.4.1.25882.2.1.1.1.1.1022) within the managed device."
   ::= { impSpeedwayR1000 1022 }

impSpeedwayR1000Indonesia OBJECT-IDENTITY
   STATUS current
   DESCRIPTION
      "OID definition for Impinj Speedway R1000 Reader in the
       Indonesia region. This is used for the sysObjectID value
       (1.3.6.1.4.1.25882.2.1.1.1.1.1023) within the managed device."
   ::= { impSpeedwayR1000 1023 }

impSpeedwayR1000NewZealand OBJECT-IDENTITY
   STATUS current
   DESCRIPTION
      "OID definition for Impinj Speedway R1000 Reader in the
       New Zealand region. This is used for the sysObjectID value
       (1.3.6.1.4.1.25882.2.1.1.1.1.1024) within the managed device."
   ::= { impSpeedwayR1000 1024 }







-- ***************************************************************
-- 
-- PRODUCT: objects that provide partitioning for the Impinj
--          Speedway Revolution R220 based on region
--
-- ***************************************************************

impSpeedwayRevR220Fcc OBJECT-IDENTITY
   STATUS current
   DESCRIPTION
      "OID definition for Impinj Speedway Revolution R220 Reader in the FCC
       region. This is used for the sysObjectID value
       (1.3.6.1.4.1.25882.2.1.2.1.1000) within the managed device."
   ::= { impSpeedwayRevR220 1000 }

impSpeedwayRevR220ETSI300-220 OBJECT-IDENTITY
   STATUS current
   DESCRIPTION
      "OID definition for Impinj Speedway Revolution R220 Reader in the 
	   ETSI EN 300-220 region. This is used for the sysObjectID value
       (1.3.6.1.4.1.25882.2.1.2.1.1001) within the managed device."
   ::= { impSpeedwayRevR220 1001 }  

impSpeedwayRevR220ETSI302-208 OBJECT-IDENTITY
   STATUS current
   DESCRIPTION
      "OID definition for Impinj Speedway Revolution R220 Reader in the 
	   ETSI EN 302-208 region. This is used for the sysObjectID value
       (1.3.6.1.4.1.25882.2.1.2.1.1002) within the managed device."
   ::= { impSpeedwayRevR220 1002 }
   
impSpeedwayRevR220HongKong OBJECT-IDENTITY
   STATUS current
   DESCRIPTION
      "OID definition for Impinj Speedway Revolution R220 Reader in the
       Hong Kong region. This is used for the sysObjectID value
       (1.3.6.1.4.1.25882.2.1.2.1.1003) within the managed device."
   ::= { impSpeedwayRevR220 1003 }

impSpeedwayRevR220Taiwan OBJECT-IDENTITY
   STATUS current
   DESCRIPTION
      "OID definition for Impinj Speedway Revolution R220 Reader in the
       Taiwan region. This is used for the sysObjectID value
       (1.3.6.1.4.1.25882.2.1.2.1.1004) within the managed device."
   ::= { impSpeedwayRevR220 1004 }

impSpeedwayRevR220Japan OBJECT-IDENTITY
   STATUS current
   DESCRIPTION
      "OID definition for Impinj Speedway Revolution R220 Reader in the Japan 
       952-954 region. This is used for the sysObjectID
       value (1.3.6.1.4.1.25882.2.1.2.1.1005) within the managed device."
   ::= { impSpeedwayRevR220 1005 }

impSpeedwayRevR220JapanLowPower OBJECT-IDENTITY
   STATUS current
   DESCRIPTION
      "OID definition for Impinj Speedway Revolution R220 Reader in the Japan 
       952-954 region using low power (<10mW). This is used for the sysObjectID
       value (1.3.6.1.4.1.25882.2.1.2.1.1006) within the managed device."
   ::= { impSpeedwayRevR220 1006 }

impSpeedwayRevR220ETSI302-208-ver1-2-1 OBJECT-IDENTITY
   STATUS current
   DESCRIPTION
      "OID definition for Impinj Speedway Revolution R220 Reader in the ETSI
       region (302.208 ver 1.2.1). This is used for the sysObjectID value
       (1.3.6.1.4.1.25882.2.1.2.1.1007) within the managed device."
   ::= { impSpeedwayRevR220 1007 }

impSpeedwayRevR220Korea OBJECT-IDENTITY
   STATUS current
   DESCRIPTION
      "OID definition for Impinj Speedway Revolution R220 Reader in the Korea region.
       This is used for the sysObjectID value (1.3.6.1.4.1.25882.2.1.2.1.1008)
       within the managed device."
   ::= { impSpeedwayRevR220 1008 }

impSpeedwayRevR220Malaysia OBJECT-IDENTITY
   STATUS current
   DESCRIPTION
      "OID definition for Impinj Speedway Revolution R220 Reader in the
       Malaysia region. This is used for the sysObjectID value
       (1.3.6.1.4.1.25882.2.1.2.1.1009) within the managed device."
   ::= { impSpeedwayRevR220 1009 }

impSpeedwayRevR220China OBJECT-IDENTITY
   STATUS current
   DESCRIPTION
      "OID definition for Impinj Speedway Revolution R220 Reader in the
       China region. This is used for the sysObjectID value
       (1.3.6.1.4.1.25882.2.1.2.1.1010) within the managed device."
   ::= { impSpeedwayRevR220 1010 }

impSpeedwayRevR220JapanNoLBT OBJECT-IDENTITY
   STATUS current
   DESCRIPTION
      "OID definition for Impinj Speedway Revolution R220 Reader in the 
	   Japan 952-954 region without LBT. This is used for the sysObjectID value 
	   (1.3.6.1.4.1.25882.2.1.2.1.1011) within the managed device."
   ::= { impSpeedwayRevR220 1011 }

impSpeedwaySouthAfrica OBJECT-IDENTITY
   STATUS current
   DESCRIPTION
      "OID definition for Impinj Revolution R220 Reader in the South Africa region.
       This is used for the sysObjectID value (1.3.6.1.4.1.25882.2.1.1.1012)
       within the managed device."
   ::= { impSpeedwayRevR220 1012 }
   
impSpeedwayRevR220Brazil OBJECT-IDENTITY
   STATUS current
   DESCRIPTION
      "OID definition for Impinj Speedway Revolution R220 Reader in the
       Brazil region. This is used for the sysObjectID value
       (1.3.6.1.4.1.25882.2.1.2.1.1013) within the managed device."
   ::= { impSpeedwayRevR220 1013 }

impSpeedwayRevR220Thailand OBJECT-IDENTITY
   STATUS current
   DESCRIPTION
      "OID definition for Impinj Speedway Revolution R220 Reader in the
       Thailand region. This is used for the sysObjectID value
       (1.3.6.1.4.1.25882.2.1.2.1.1014) within the managed device."
   ::= { impSpeedwayRevR220 1014 }

impSpeedwayRevR220Singapore OBJECT-IDENTITY
   STATUS current
   DESCRIPTION
      "OID definition for Impinj Speedway Revolution R220 Reader in the
       Singapore region. This is used for the sysObjectID value
       (1.3.6.1.4.1.25882.2.1.2.1.1015) within the managed device."
   ::= { impSpeedwayRevR220 1015 }

impSpeedwayRevR220Australia OBJECT-IDENTITY
   STATUS current
   DESCRIPTION
      "OID definition for Impinj Speedway Revolution R220 Reader in the
       Australia region. This is used for the sysObjectID value
       (1.3.6.1.4.1.25882.2.1.2.1.1016) within the managed device."
   ::= { impSpeedwayRevR220 1016 }

impSpeedwayRevR220India OBJECT-IDENTITY
   STATUS current
   DESCRIPTION
      "OID definition for Impinj Speedway Revolution R220 Reader in the
       India region. This is used for the sysObjectID value
       (1.3.6.1.4.1.25882.2.1.2.1.1017) within the managed device."
   ::= { impSpeedwayRevR220 1017 }

impSpeedwayRevR220Uruguay OBJECT-IDENTITY
   STATUS current
   DESCRIPTION
      "OID definition for Impinj Speedway Revolution R220 Reader in the
       Uruguay region. This is used for the sysObjectID value
       (1.3.6.1.4.1.25882.2.1.2.1.1018) within the managed device."
   ::= { impSpeedwayRevR220 1018 }

impSpeedwayRevR220Vietnam OBJECT-IDENTITY
   STATUS current
   DESCRIPTION
      "OID definition for Impinj Speedway Revolution R220 Reader in the
       Vietnam region. This is used for the sysObjectID value
       (1.3.6.1.4.1.25882.2.1.2.1.1019) within the managed device."
   ::= { impSpeedwayRevR220 1019 }

impSpeedwayRevR220Israel OBJECT-IDENTITY
   STATUS current
   DESCRIPTION
      "OID definition for Impinj Speedway Revolution R220 Reader in the
       Israel region. This is used for the sysObjectID value
       (1.3.6.1.4.1.25882.2.1.2.1.1020) within the managed device."
   ::= { impSpeedwayRevR220 1020 }

impSpeedwayRev220Philippines OBJECT-IDENTITY
   STATUS current
   DESCRIPTION
      "OID definition for Impinj Speedway Revolution R220 Reader in the
       Philippines region. This is used for the sysObjectID value
       (1.3.6.1.4.1.25882.2.1.2.1.1021) within the managed device."
   ::= { impSpeedwayRevR220 1021 }

impSpeedwayRev220CanadaPost OBJECT-IDENTITY
   STATUS current
   DESCRIPTION
      "OID definition for Impinj Speedway Revolution R220 Reader in the
       CanadaPost region. This is used for the sysObjectID value
       (1.3.6.1.4.1.25882.2.1.2.1.1022) within the managed device."
   ::= { impSpeedwayRevR220 1022 }

impSpeedwayRev220Indonesia OBJECT-IDENTITY
   STATUS current
   DESCRIPTION
      "OID definition for Impinj Speedway Revolution R220 Reader in the
       Indonesia region. This is used for the sysObjectID value
       (1.3.6.1.4.1.25882.2.1.2.1.1023) within the managed device."
   ::= { impSpeedwayRevR220 1023 }

impSpeedwayRev220NewZealand OBJECT-IDENTITY
   STATUS current
   DESCRIPTION
      "OID definition for Impinj Speedway Revolution R220 Reader in the
       New Zealand region. This is used for the sysObjectID value
       (1.3.6.1.4.1.25882.2.1.2.1.1024) within the managed device."
   ::= { impSpeedwayRevR220 1024 }








-- ***************************************************************
-- 
-- PRODUCT: objects that provide partitioning for the Impinj
--          Speedway Revolution R420 based on region
--
-- ***************************************************************

impSpeedwayRevR420Fcc OBJECT-IDENTITY
   STATUS current
   DESCRIPTION
      "OID definition for Impinj Speedway Revolution R420 Reader in the FCC
       region. This is used for the sysObjectID value
       (1.3.6.1.4.1.25882.2.1.2.2.1000) within the managed device."
   ::= { impSpeedwayRevR420 1000 }

impSpeedwayRevR420ETSI300-220 OBJECT-IDENTITY
   STATUS current
   DESCRIPTION
      "OID definition for Impinj Speedway Revolution R420 Reader in the 
	   ETSI EN 300-220 region. This is used for the sysObjectID value
       (1.3.6.1.4.1.25882.2.1.2.2.1001) within the managed device."
   ::= { impSpeedwayRevR420 1001 }  

impSpeedwayRevR420ETSI302-208 OBJECT-IDENTITY
   STATUS current
   DESCRIPTION
      "OID definition for Impinj Speedway Revolution R420 Reader in the 
	   ETSI EN 302-208 region. This is used for the sysObjectID value
       (1.3.6.1.4.1.25882.2.1.2.2.1002) within the managed device."
   ::= { impSpeedwayRevR420 1002 }
   
impSpeedwayRevR420HongKong OBJECT-IDENTITY
   STATUS current
   DESCRIPTION
      "OID definition for Impinj Speedway Revolution R420 Reader in the Hong
       Kong region. This is used for the sysObjectID value
       (1.3.6.1.4.1.25882.2.1.2.2.1003) within the managed device."
   ::= { impSpeedwayRevR420 1003 }

impSpeedwayRevR420Taiwan OBJECT-IDENTITY
   STATUS current
   DESCRIPTION
      "OID definition for Impinj Speedway Revolution R420 Reader in the Taiwan
       region. This is used for the sysObjectID value
       (1.3.6.1.4.1.25882.2.1.2.2.1004) within the managed device."
   ::= { impSpeedwayRevR420 1004 }

impSpeedwayRevR420Japan OBJECT-IDENTITY
   STATUS current
   DESCRIPTION
      "OID definition for Impinj Speedway Revolution R420 Reader in the Japan 
       952-954 region. This is used for the sysObjectID
       value (1.3.6.1.4.1.25882.2.1.2.2.1005) within the managed device."
   ::= { impSpeedwayRevR420 1005 }

impSpeedwayRevR420JapanLowPower OBJECT-IDENTITY
   STATUS current
   DESCRIPTION
      "OID definition for Impinj Speedway Revolution R420 Reader in the Japan 
       952-954 region using low power (<10mW). This is used for the sysObjectID
       value (1.3.6.1.4.1.25882.2.1.2.2.1006) within the managed device."
   ::= { impSpeedwayRevR420 1006 }

impSpeedwayRevR420ETSI302-208-ver1-2-1 OBJECT-IDENTITY
   STATUS current
   DESCRIPTION
      "OID definition for Impinj Speedway Revolution R420 Reader in the ETSI
       302.208 ver 1.2.1 region. This is used for the sysObjectID value
       (1.3.6.1.4.1.25882.2.1.2.2.1007) within the managed device."
   ::= { impSpeedwayRevR420 1007 }

impSpeedwayRevR420Korea OBJECT-IDENTITY
   STATUS current
   DESCRIPTION
      "OID definition for Impinj Speedway Revolution R420 Reader in the Korea region.
       This is used for the sysObjectID value (1.3.6.1.4.1.25882.2.1.2.2.1008)
       within the managed device."
   ::= { impSpeedwayRevR420 1008 }

impSpeedwayRevR420Malaysia OBJECT-IDENTITY
   STATUS current
   DESCRIPTION
      "OID definition for Impinj Speedway Revolution R420 Reader in the
       Malaysia region. This is used for the sysObjectID value
       (1.3.6.1.4.1.25882.2.1.2.2.1009) within the managed device."
   ::= { impSpeedwayRevR420 1009 }

impSpeedwayRevR420China OBJECT-IDENTITY
   STATUS current
   DESCRIPTION
      "OID definition for Impinj Speedway Revolution R420 Reader in the
       China region. This is used for the sysObjectID value
       (1.3.6.1.4.1.25882.2.1.2.2.1010) within the managed device."
   ::= { impSpeedwayRevR420 1010 }

impSpeedwayRevR420JapanNoLBT OBJECT-IDENTITY
   STATUS current
   DESCRIPTION
      "OID definition for Impinj Speedway Revolution R420 Reader in the 
	   Japan 952-954 region without LBT. This is used for the sysObjectID value 
	   (1.3.6.1.4.1.25882.2.1.2.2.1011) within the managed device."
   ::= { impSpeedwayRevR420 1011 }

impSpeedwayRevR420SouthAfrica OBJECT-IDENTITY
   STATUS current
   DESCRIPTION
      "OID definition for Impinj Speedway Revolution R420 Reader in the South Africa region.
       This is used for the sysObjectID value (1.3.6.1.4.1.25882.2.1.1.2.1012)
       within the managed device."
   ::= { impSpeedwayRevR420 1012 }

impSpeedwayRevR420Brazil OBJECT-IDENTITY
   STATUS current
   DESCRIPTION
      "OID definition for Impinj Speedway Revolution R420 Reader in the
       Brazil region. This is used for the sysObjectID value
       (1.3.6.1.4.1.25882.2.1.2.2.1013) within the managed device."
   ::= { impSpeedwayRevR420 1013 }

impSpeedwayRevR420Thailand OBJECT-IDENTITY
   STATUS current
   DESCRIPTION
      "OID definition for Impinj Speedway Revolution R420 Reader in the
       Thailand region. This is used for the sysObjectID value
       (1.3.6.1.4.1.25882.2.1.2.2.1014) within the managed device."
   ::= { impSpeedwayRevR420 1014 }

impSpeedwayRevR420Singapore OBJECT-IDENTITY
   STATUS current
   DESCRIPTION
      "OID definition for Impinj Speedway Revolution R420 Reader in the
       Singapore region. This is used for the sysObjectID value
       (1.3.6.1.4.1.25882.2.1.2.2.1015) within the managed device."
   ::= { impSpeedwayRevR420 1015 }

impSpeedwayRevR420Australia OBJECT-IDENTITY
   STATUS current
   DESCRIPTION
      "OID definition for Impinj Speedway Revolution R420 Reader in the
       Australia region. This is used for the sysObjectID value
       (1.3.6.1.4.1.25882.2.1.2.2.1016) within the managed device."
   ::= { impSpeedwayRevR420 1016 }

impSpeedwayRevR420India OBJECT-IDENTITY
   STATUS current
   DESCRIPTION
      "OID definition for Impinj Speedway Revolution R420 Reader in the
       India region. This is used for the sysObjectID value
       (1.3.6.1.4.1.25882.2.1.2.2.1017) within the managed device."
   ::= { impSpeedwayRevR420 1017 }

impSpeedwayRevR420Uruguay OBJECT-IDENTITY
   STATUS current
   DESCRIPTION
      "OID definition for Impinj Speedway Revolution R420 Reader in the
       Uruguay region. This is used for the sysObjectID value
       (1.3.6.1.4.1.25882.2.1.2.2.1018) within the managed device."
   ::= { impSpeedwayRevR420 1018 }

impSpeedwayRevR420Vietnam OBJECT-IDENTITY
   STATUS current
   DESCRIPTION
      "OID definition for Impinj Speedway Revolution R420 Reader in the
       Vietnam region. This is used for the sysObjectID value
       (1.3.6.1.4.1.25882.2.1.2.2.1019) within the managed device."
   ::= { impSpeedwayRevR420 1019 }

impSpeedwayRevR420Israel OBJECT-IDENTITY
   STATUS current
   DESCRIPTION
      "OID definition for Impinj Speedway Revolution R420 Reader in the
       Israel region. This is used for the sysObjectID value
       (1.3.6.1.4.1.25882.2.1.2.2.1020) within the managed device."
   ::= { impSpeedwayRevR420 1020 }

impSpeedwayRevR420Philippines OBJECT-IDENTITY
   STATUS current
   DESCRIPTION
      "OID definition for Impinj Speedway Revolution R420 Reader in the
       Philippines region. This is used for the sysObjectID value
       (1.3.6.1.4.1.25882.2.1.2.2.1021) within the managed device."
   ::= { impSpeedwayRevR420 1021 }

impSpeedwayRevR420CanadaPost OBJECT-IDENTITY
   STATUS current
   DESCRIPTION
      "OID definition for Impinj Speedway Revolution R420 Reader in the
       CanadaPost region. This is used for the sysObjectID value
       (1.3.6.1.4.1.25882.2.1.2.2.1022) within the managed device."
   ::= { impSpeedwayRevR420 1022 }

impSpeedwayRevR420Indonesia OBJECT-IDENTITY
   STATUS current
   DESCRIPTION
      "OID definition for Impinj Speedway Revolution R420 Reader in the
       Indonesia region. This is used for the sysObjectID value
       (1.3.6.1.4.1.25882.2.1.2.2.1023) within the managed device."
   ::= { impSpeedwayRevR420 1023 }

impSpeedwayRevR420NewZealand OBJECT-IDENTITY
   STATUS current
   DESCRIPTION
      "OID definition for Impinj Speedway Revolution R420 Reader in the
       New Zealand region. This is used for the sysObjectID value
       (1.3.6.1.4.1.25882.2.1.2.2.1024) within the managed device."
   ::= { impSpeedwayRevR420 1024 }





-- ***************************************************************
-- 
-- PRODUCT: objects that provide partitioning for the Impinj
--          xArray R660 based on region
--
-- ***************************************************************

impSpeedwayRevR660Fcc OBJECT-IDENTITY
   STATUS current
   DESCRIPTION
      "OID definition for Impinj xArray R660 Reader in the FCC
       region. This is used for the sysObjectID value
       (1.3.6.1.4.1.25882.2.1.2.3.1000) within the managed device."
   ::= { impSpeedwayRevR660 1000 }



-- ***************************************************************
-- 
-- PRODUCT: objects that provide partitioning for the Impinj
--          xArray R680 based on region
--
-- ***************************************************************

impSpeedwayRevR680Fcc OBJECT-IDENTITY
   STATUS current
   DESCRIPTION
      "OID definition for Impinj xArray R680 Reader in the FCC
       region. This is used for the sysObjectID value
       (1.3.6.1.4.1.25882.2.1.2.7.1000) within the managed device."
   ::= { impSpeedwayRevR680 1000 }

impSpeedwayRevR680ETSI300-220 OBJECT-IDENTITY
   STATUS current
   DESCRIPTION
      "OID definition for Impinj Speedway Revolution R680 Reader in the 
	   ETSI EN 300-220 region. This is used for the sysObjectID value
       (1.3.6.1.4.1.25882.2.1.2.7.1001) within the managed device."
   ::= { impSpeedwayRevR680 1001 }  

impSpeedwayRevR680ETSI302-208 OBJECT-IDENTITY
   STATUS current
   DESCRIPTION
      "OID definition for Impinj Speedway Revolution R680 Reader in the 
	   ETSI EN 302-208 region. This is used for the sysObjectID value
       (1.3.6.1.4.1.25882.2.1.2.7.1002) within the managed device."
   ::= { impSpeedwayRevR680 1002 }
   
impSpeedwayRevR680HongKong OBJECT-IDENTITY
   STATUS current
   DESCRIPTION
      "OID definition for Impinj Speedway Revolution R680 Reader in the Hong
       Kong region. This is used for the sysObjectID value
       (1.3.6.1.4.1.25882.2.1.2.7.1003) within the managed device."
   ::= { impSpeedwayRevR680 1003 }

impSpeedwayRevR680Taiwan OBJECT-IDENTITY
   STATUS current
   DESCRIPTION
      "OID definition for Impinj Speedway Revolution R680 Reader in the Taiwan
       region. This is used for the sysObjectID value
       (1.3.6.1.4.1.25882.2.1.2.7.1004) within the managed device."
   ::= { impSpeedwayRevR680 1004 }

impSpeedwayRevR680Japan OBJECT-IDENTITY
   STATUS current
   DESCRIPTION
      "OID definition for Impinj Speedway Revolution R680 Reader in the Japan 
       952-954 region. This is used for the sysObjectID
       value (1.3.6.1.4.1.25882.2.1.2.7.1005) within the managed device."
   ::= { impSpeedwayRevR680 1005 }

impSpeedwayRevR680JapanLowPower OBJECT-IDENTITY
   STATUS current
   DESCRIPTION
      "OID definition for Impinj Speedway Revolution R680 Reader in the Japan 
       952-954 region using low power (<10mW). This is used for the sysObjectID
       value (1.3.6.1.4.1.25882.2.1.2.7.1006) within the managed device."
   ::= { impSpeedwayRevR680 1006 }

impSpeedwayRevR680ETSI302-208-ver1-2-1 OBJECT-IDENTITY
   STATUS current
   DESCRIPTION
      "OID definition for Impinj Speedway Revolution R680 Reader in the ETSI
       302.208 ver 1.2.1 region. This is used for the sysObjectID value
       (1.3.6.1.4.1.25882.2.1.2.7.1007) within the managed device."
   ::= { impSpeedwayRevR680 1007 }

impSpeedwayRevR680Korea OBJECT-IDENTITY
   STATUS current
   DESCRIPTION
      "OID definition for Impinj Speedway Revolution R680 Reader in the Korea region.
       This is used for the sysObjectID value (1.3.6.1.4.1.25882.2.1.2.7.1008)
       within the managed device."
   ::= { impSpeedwayRevR680 1008 }

impSpeedwayRevR680Malaysia OBJECT-IDENTITY
   STATUS current
   DESCRIPTION
      "OID definition for Impinj Speedway Revolution R680 Reader in the
       Malaysia region. This is used for the sysObjectID value
       (1.3.6.1.4.1.25882.2.1.2.7.1009) within the managed device."
   ::= { impSpeedwayRevR680 1009 }

impSpeedwayRevR680China OBJECT-IDENTITY
   STATUS current
   DESCRIPTION
      "OID definition for Impinj Speedway Revolution R680 Reader in the
       China region. This is used for the sysObjectID value
       (1.3.6.1.4.1.25882.2.1.2.7.1010) within the managed device."
   ::= { impSpeedwayRevR680 1010 }

impSpeedwayRevR680JapanNoLBT OBJECT-IDENTITY
   STATUS current
   DESCRIPTION
      "OID definition for Impinj Speedway Revolution R680 Reader in the 
	   Japan 952-954 region without LBT. This is used for the sysObjectID value 
	   (1.3.6.1.4.1.25882.2.1.2.7.1011) within the managed device."
   ::= { impSpeedwayRevR680 1011 }

impSpeedwayRevR680SouthAfrica OBJECT-IDENTITY
   STATUS current
   DESCRIPTION
      "OID definition for Impinj Speedway Revolution R680 Reader in the South Africa region.
       This is used for the sysObjectID value (1.3.6.1.4.1.25882.2.1.1.7.1012)
       within the managed device."
   ::= { impSpeedwayRevR680 1012 }

impSpeedwayRevR680Brazil OBJECT-IDENTITY
   STATUS current
   DESCRIPTION
      "OID definition for Impinj Speedway Revolution R680 Reader in the
       Brazil region. This is used for the sysObjectID value
       (1.3.6.1.4.1.25882.2.1.2.7.1013) within the managed device."
   ::= { impSpeedwayRevR680 1013 }

impSpeedwayRevR680Thailand OBJECT-IDENTITY
   STATUS current
   DESCRIPTION
      "OID definition for Impinj Speedway Revolution R680 Reader in the
       Thailand region. This is used for the sysObjectID value
       (1.3.6.1.4.1.25882.2.1.2.7.1014) within the managed device."
   ::= { impSpeedwayRevR680 1014 }

impSpeedwayRevR680Singapore OBJECT-IDENTITY
   STATUS current
   DESCRIPTION
      "OID definition for Impinj Speedway Revolution R680 Reader in the
       Singapore region. This is used for the sysObjectID value
       (1.3.6.1.4.1.25882.2.1.2.7.1015) within the managed device."
   ::= { impSpeedwayRevR680 1015 }

impSpeedwayRevR680Australia OBJECT-IDENTITY
   STATUS current
   DESCRIPTION
      "OID definition for Impinj Speedway Revolution R680 Reader in the
       Australia region. This is used for the sysObjectID value
       (1.3.6.1.4.1.25882.2.1.2.7.1016) within the managed device."
   ::= { impSpeedwayRevR680 1016 }

impSpeedwayRevR680India OBJECT-IDENTITY
   STATUS current
   DESCRIPTION
      "OID definition for Impinj Speedway Revolution R680 Reader in the
       India region. This is used for the sysObjectID value
       (1.3.6.1.4.1.25882.2.1.2.7.1017) within the managed device."
   ::= { impSpeedwayRevR680 1017 }

impSpeedwayRevR680Uruguay OBJECT-IDENTITY
   STATUS current
   DESCRIPTION
      "OID definition for Impinj Speedway Revolution R680 Reader in the
       Uruguay region. This is used for the sysObjectID value
       (1.3.6.1.4.1.25882.2.1.2.7.1018) within the managed device."
   ::= { impSpeedwayRevR680 1018 }

impSpeedwayRevR680Vietnam OBJECT-IDENTITY
   STATUS current
   DESCRIPTION
      "OID definition for Impinj Speedway Revolution R680 Reader in the
       Vietnam region. This is used for the sysObjectID value
       (1.3.6.1.4.1.25882.2.1.2.7.1019) within the managed device."
   ::= { impSpeedwayRevR680 1019 }

impSpeedwayRevR680Israel OBJECT-IDENTITY
   STATUS current
   DESCRIPTION
      "OID definition for Impinj Speedway Revolution R680 Reader in the
       Israel region. This is used for the sysObjectID value
       (1.3.6.1.4.1.25882.2.1.2.7.1020) within the managed device."
   ::= { impSpeedwayRevR680 1020 }

impSpeedwayRevR680Philippines OBJECT-IDENTITY
   STATUS current
   DESCRIPTION
      "OID definition for Impinj Speedway Revolution R680 Reader in the
       Philippines region. This is used for the sysObjectID value
       (1.3.6.1.4.1.25882.2.1.2.7.1021) within the managed device."
   ::= { impSpeedwayRevR680 1021 }

impSpeedwayRevR680CanadaPost OBJECT-IDENTITY
   STATUS current
   DESCRIPTION
      "OID definition for Impinj Speedway Revolution R680 Reader in the
       CanadaPost region. This is used for the sysObjectID value
       (1.3.6.1.4.1.25882.2.1.2.7.1022) within the managed device."
   ::= { impSpeedwayRevR680 1022 }

impSpeedwayRevR680Indonesia OBJECT-IDENTITY
   STATUS current
   DESCRIPTION
      "OID definition for Impinj Speedway Revolution R680 Reader in the
       Indonesia region. This is used for the sysObjectID value
       (1.3.6.1.4.1.25882.2.1.2.7.1023) within the managed device."
   ::= { impSpeedwayRevR680 1023 }

impSpeedwayRevR680NewZealand OBJECT-IDENTITY
   STATUS current
   DESCRIPTION
      "OID definition for Impinj Speedway Revolution R680 Reader in the
       New Zealand region. This is used for the sysObjectID value
       (1.3.6.1.4.1.25882.2.1.2.7.1024) within the managed device."
   ::= { impSpeedwayRevR680 1024 }




-- ***************************************************************
-- 
-- PRODUCT: objects that provide partitioning for the Impinj
--          Speedway R1000 with wireless support based on region
--
-- ***************************************************************

impSpeedwayWirelessLanFcc OBJECT-IDENTITY
   STATUS current
   DESCRIPTION
      "OID definition for Impinj Speedway R1000 Reader with wireless
       support in the FCC region. This is used for the sysObjectID value
       (1.3.6.1.4.1.25882.2.1.3.1000) within the managed device."
   ::= { impSpeedwayWirelessLan 1000 }

-- ***************************************************************
-- 
-- PRODUCT: objects that provide partitioning for the Impinj
--          Speedway R1000 with wireless support based on region
--
-- ***************************************************************

impMicroneticsRFIDForkliftSystemFcc OBJECT-IDENTITY
   STATUS current
   DESCRIPTION
      "OID definition for Impinj powered Micronetics RFID Forklift system
       Reader in the FCC region. This is used for the sysObjectID value
       (1.3.6.1.4.1.25882.2.1.4.1000) within the managed device."
   ::= { impMicroneticsRFIDForkliftSystem 1000 }

-- ***************************************************************
-- 
-- PRODUCT: objects that provide further partitioning for the Impinj
--          product types
--
-- ***************************************************************

impController OBJECT-IDENTITY
   STATUS current
   DESCRIPTION
      "Root for definition of Impinj RFID Controller products."
   ::= { impProduct 2 }

impPosController OBJECT-IDENTITY
   STATUS current
   DESCRIPTION
      "OID definition for Impinj POS RFID Controller. This is used for the
       sysObjectID value (1.3.6.1.4.1.25882.2.2.1) within the managed
       device."
   ::= { impController 1 }

END
