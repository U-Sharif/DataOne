--
-- IMPINJ-R680-MIB.mib
-- MIB generated by MG-SOFT Visual MIB Builder 2010 Version 8.0  Build 410
-- Friday, September 23, 2011 at 13:53:34
--

--  IMPINJ-R680-MIB.mib
-- MIB generated by MG-SOFT Visual MIB Builder 2010 Version 8.0  Build 410
-- Wednesday, September 21, 2011 at 17:26:41
-- 
--  IMPINJ-R680-MIB.txt
-- MIB generated by MG-SOFT Visual MIB Builder 2010 Version 8.0  Build 410
-- Monday, September 19, 2011 at 15:59:21
-- 
--   **************************************************************
-- *
-- * IMPINJ-R680-MIB.txt: The Impinj xArray MIB
-- *
-- * DESCRIPTION: This MIB describes variables and traps provided
-- *              by the Impinj xArray product.
-- *
-- * Copyright (c) 2011 Impinj, Inc.
-- * All Rights Reserved - Licensed Software
-- * 
-- **************************************************************

	IMPINJ-R680-MIB DEFINITIONS ::= BEGIN
 
		IMPORTS
			impSpeedwayRevR680			
				FROM IMPINJ-ROOT-REG-MIB			
			Integer32, Unsigned32, OBJECT-TYPE			
				FROM SNMPv2-SMI;
	
	
--
-- Node definitions
--
	
--  Node definitions
-- 
-- Node definitions
-- 
-- The enterprise ID assigned to Impinj by the IANA: 25882.
-- 
-- 1.3.6.1.4.1.25882.2.1.2.7
-- Sept 16, 2006 at 12:00 GMT
-- Sept 16, 2006 at 12:00 GMT
-- 
-- Node definitions
-- 
-- 1.3.6.1.4.1.25882.2.1.2.7.1
-- 1.3.6.1.4.1.25882.2.1.2.7.1
-- 1.3.6.1.4.1.25882.2.1.2.7.1
		-- 1.3.6.1.4.1.25882.2.1.2.7.1
		arrayObjects OBJECT IDENTIFIER ::= { impSpeedwayRevR680 1 }

		
--    This section represents objects pertaining to the array hardware.
-- 1.3.6.1.4.1.25882.2.1.2.7.1.1
-- 1.3.6.1.4.1.25882.2.1.2.7.1.1
-- 1.3.6.1.4.1.25882.2.1.2.7.1.1
		-- 1.3.6.1.4.1.25882.2.1.2.7.1.1
		arrayController OBJECT IDENTIFIER ::= { arrayObjects 1 }

		
--   1.3.6.1.4.1.25882.2.1.2.7.1.1.2
-- 1.3.6.1.4.1.25882.2.1.2.7.1.1.2
		-- 1.3.6.1.4.1.25882.2.1.2.7.1.1.1
		serialNumber OBJECT-TYPE
			SYNTAX OCTET STRING
			MAX-ACCESS read-only
			STATUS current
			DESCRIPTION
				"This variable reports the hardware serial number
				corresponding to the array MUX Controller. This 
				variable is a free-form string."
			::= { arrayController 1 }

		
--   1.3.6.1.4.1.25882.2.1.2.7.1.1.3
-- 1.3.6.1.4.1.25882.2.1.2.7.1.1.3
		-- 1.3.6.1.4.1.25882.2.1.2.7.1.1.2
		pcbaVersion OBJECT-TYPE
			SYNTAX OCTET STRING
			MAX-ACCESS read-only
			STATUS current
			DESCRIPTION
				"This variable reports the hardware PCBA revision 
				number corresponding to the array MUX Controller 
				device. This variable is a free-form string."
			::= { arrayController 2 }

		
--    1.3.6.1.4.1.25882.2.1.2.7.1.1.1
-- 1.3.6.1.4.1.25882.2.1.2.7.1.1.4
-- 1.3.6.1.4.1.25882.2.1.2.7.1.1.4
		-- 1.3.6.1.4.1.25882.2.1.2.7.1.1.3
		firmwareVersion OBJECT-TYPE
			SYNTAX OCTET STRING
			MAX-ACCESS read-only
			STATUS current
			DESCRIPTION
				"This variable reports the firmware version number
				corresponding to the array MUX Controller device.
				This variable is a free-form string."
			::= { arrayController 3 }

		
		-- 1.3.6.1.4.1.25882.2.1.2.7.1.1.4
		beaconState OBJECT-TYPE
			SYNTAX INTEGER
				{
				enabled(1),
				disabled(2)
				}
			MAX-ACCESS read-only
			STATUS current
			DESCRIPTION
				"Description."
			::= { arrayController 4 }

		
--   This class of variables are used to report the 
-- physical orientation of the array device.
-- 1.3.6.1.4.1.25882.2.1.2.7.1.1.5
-- 1.3.6.1.4.1.25882.2.1.2.7.1.1.5
		-- 1.3.6.1.4.1.25882.2.1.2.7.1.1.5
		arrayTiltSensor OBJECT IDENTIFIER ::= { arrayController 5 }

		
--   1.3.6.1.4.1.25882.2.1.2.7.1.1.5.1
-- 1.3.6.1.4.1.25882.2.1.2.7.1.1.5.1
		-- 1.3.6.1.4.1.25882.2.1.2.7.1.1.5.1
		xaxis OBJECT-TYPE
			SYNTAX Integer32
			UNITS "degrees"
			MAX-ACCESS read-only
			STATUS current
			DESCRIPTION
				"This variable reports the current array orientation 
				as measured on the x-axis"
			::= { arrayTiltSensor 1 }

		
--   1.3.6.1.4.1.25882.2.1.2.7.1.1.5.2
-- 1.3.6.1.4.1.25882.2.1.2.7.1.1.5.2
		-- 1.3.6.1.4.1.25882.2.1.2.7.1.1.5.2
		yaxis OBJECT-TYPE
			SYNTAX Integer32
			UNITS "degrees"
			MAX-ACCESS read-only
			STATUS current
			DESCRIPTION
				"This variable reports the current array orientation 
				as measured on the y-axis"
			::= { arrayTiltSensor 2 }

		
--   1.3.6.1.4.1.25882.2.1.2.7.1.1.5.3
-- 1.3.6.1.4.1.25882.2.1.2.7.1.1.5.3
		-- 1.3.6.1.4.1.25882.2.1.2.7.1.1.5.3
		zaxis OBJECT-TYPE
			SYNTAX Integer32
			UNITS "degrees"
			MAX-ACCESS read-only
			STATUS current
			DESCRIPTION
				"This variable reports the current array orientation 
				as measured on the z-axis"
			::= { arrayTiltSensor 3 }

		
--   1.3.6.1.4.1.25882.2.1.2.7.1.3
-- 1.3.6.1.4.1.25882.2.1.2.7.1.3
		-- 1.3.6.1.4.1.25882.2.1.2.7.1.3
		antennaHysteresis OBJECT IDENTIFIER ::= { arrayObjects 3 }

		
--   1.3.6.1.4.1.25882.2.1.2.7.1.3.1
-- 1.3.6.1.4.1.25882.2.1.2.7.1.3.1
		-- 1.3.6.1.4.1.25882.2.1.2.7.1.3.1
		arrayAntennaHysteresisConnectedTimer OBJECT-TYPE
			SYNTAX Unsigned32
			UNITS "milliseconds"
			MAX-ACCESS read-only
			STATUS current
			DESCRIPTION
				"Number of milliseconds that an antenna must be 
				considered connected before an antenna connected 
				notification is sent and the epcg status of the 
				antenna is set to connected."
			::= { antennaHysteresis 1 }

		
--   1.3.6.1.4.1.25882.2.1.2.7.1.3.2
-- 1.3.6.1.4.1.25882.2.1.2.7.1.3.2
		-- 1.3.6.1.4.1.25882.2.1.2.7.1.3.2
		arrayAntennaHysteresisDisconnectedTimer OBJECT-TYPE
			SYNTAX Unsigned32
			UNITS "milliseconds"
			MAX-ACCESS read-only
			STATUS current
			DESCRIPTION
				"Number of milliseconds that an antenna must be 
				considered disconnected before an antenna disconnected 
				notification is sent and the epcg status of the 
				antenna is set to disconnected."
			::= { antennaHysteresis 2 }

		
--   1.3.6.1.4.1.25882.2.1.2.7.1.3.3
-- 1.3.6.1.4.1.25882.2.1.2.7.1.3.3
		-- 1.3.6.1.4.1.25882.2.1.2.7.1.3.3
		arrayAntennaHysteresisTable OBJECT-TYPE
			SYNTAX SEQUENCE OF ArrayAntennaHysteresisEntry
			MAX-ACCESS not-accessible
			STATUS current
			DESCRIPTION
				"A table containing hysteresis information for each
				beam in an array device."
			::= { antennaHysteresis 3 }

		
--   1.3.6.1.4.1.25882.2.1.2.7.1.3.3.1
-- 1.3.6.1.4.1.25882.2.1.2.7.1.3.3.1
		-- 1.3.6.1.4.1.25882.2.1.2.7.1.3.3.1
		arrayAntennaHysteresisEntry OBJECT-TYPE
			SYNTAX ArrayAntennaHysteresisEntry
			MAX-ACCESS not-accessible
			STATUS current
			DESCRIPTION
				"Antenna Hysteresis Table Entry"
			INDEX { arrayAntennaIndex }
			::= { arrayAntennaHysteresisTable 1 }

		
		ArrayAntennaHysteresisEntry ::=
			SEQUENCE { 
				arrayAntennaIndex
					Integer32,
				arrayAntennaCurrentStatus
					INTEGER,
				arrayAntennaHysteresisTimerActive
					INTEGER,
				arrayAntennaHysteresisTimeRemaining
					Unsigned32
			 }

--   1.3.6.1.4.1.25882.2.1.2.7.1.3.3.1.1
-- 1.3.6.1.4.1.25882.2.1.2.7.1.3.3.1.1
		-- 1.3.6.1.4.1.25882.2.1.2.7.1.3.3.1.1
		arrayAntennaIndex OBJECT-TYPE
			SYNTAX Integer32 (1..1000)
			MAX-ACCESS read-only
			STATUS current
			DESCRIPTION
				"An index of each antenna connection."
			::= { arrayAntennaHysteresisEntry 1 }

		
--   1.3.6.1.4.1.25882.2.1.2.7.1.3.3.1.2
-- 1.3.6.1.4.1.25882.2.1.2.7.1.3.3.1.2
		-- 1.3.6.1.4.1.25882.2.1.2.7.1.3.3.1.2
		arrayAntennaCurrentStatus OBJECT-TYPE
			SYNTAX INTEGER
				{
				connected(1),
				disconnected(2)
				}
			MAX-ACCESS read-only
			STATUS current
			DESCRIPTION
				"The realtime status of the specified antenna."
			::= { arrayAntennaHysteresisEntry 2 }

		
--   1.3.6.1.4.1.25882.2.1.2.7.1.3.3.1.3
-- 1.3.6.1.4.1.25882.2.1.2.7.1.3.3.1.3
		-- 1.3.6.1.4.1.25882.2.1.2.7.1.3.3.1.3
		arrayAntennaHysteresisTimerActive OBJECT-TYPE
			SYNTAX INTEGER
				{
				active(1),
				inactive(2)
				}
			MAX-ACCESS read-only
			STATUS current
			DESCRIPTION
				"Boolean indicating whether or not an antenna's 
				status is currently being histeresisized."
			::= { arrayAntennaHysteresisEntry 3 }

		
--   1.3.6.1.4.1.25882.2.1.2.7.1.3.3.1.4
-- 1.3.6.1.4.1.25882.2.1.2.7.1.3.3.1.4
		-- 1.3.6.1.4.1.25882.2.1.2.7.1.3.3.1.4
		arrayAntennaHysteresisTimeRemaining OBJECT-TYPE
			SYNTAX Unsigned32
			UNITS "milliseconds"
			MAX-ACCESS read-only
			STATUS current
			DESCRIPTION
				"Number of milliseconds before antenna event triggered."
			::= { arrayAntennaHysteresisEntry 4 }

		
--   1.3.6.1.4.1.25882.2.1.2.7.1.4
-- 1.3.6.1.4.1.25882.2.1.2.7.1.4
		-- 1.3.6.1.4.1.25882.2.1.2.7.1.4
		arrayConfiguration OBJECT IDENTIFIER ::= { arrayObjects 4 }

		
--   1.3.6.1.4.1.25882.2.1.2.7.1.4.1
-- 1.3.6.1.4.1.25882.2.1.2.7.1.4.1
		-- 1.3.6.1.4.1.25882.2.1.2.7.1.4.1
		arrayCurrentRole OBJECT-TYPE
			SYNTAX INTEGER
				{
				generic(1),
				scanning(2),
				direction(3),
				location(4)
				}
			MAX-ACCESS read-only
			STATUS current
			DESCRIPTION
				"The current array role."
			::= { arrayConfiguration 1 }

		
--   1.3.6.1.4.1.25882.2.1.2.7.1.4.2
-- 1.3.6.1.4.1.25882.2.1.2.7.1.4.2
		-- 1.3.6.1.4.1.25882.2.1.2.7.1.4.2
		arraySectorConfigurationTable OBJECT-TYPE
			SYNTAX SEQUENCE OF ArraySectorConfigurationEntry
			MAX-ACCESS not-accessible
			STATUS current
			DESCRIPTION
				"Description."
			::= { arrayConfiguration 2 }

		
--   1.3.6.1.4.1.25882.2.1.2.7.1.4.2.1
-- 1.3.6.1.4.1.25882.2.1.2.7.1.4.2.1
		-- 1.3.6.1.4.1.25882.2.1.2.7.1.4.2.1
		arraySectorConfigurationEntry OBJECT-TYPE
			SYNTAX ArraySectorConfigurationEntry
			MAX-ACCESS not-accessible
			STATUS current
			DESCRIPTION
				"Description."
			INDEX { arrayAntennaIndex }
			::= { arraySectorConfigurationTable 1 }

		
		ArraySectorConfigurationEntry ::=
			SEQUENCE { 
				arraySectorTableIndex
					Integer32,
				arraySectorID
					Integer32
			 }

--   1.3.6.1.4.1.25882.2.1.2.7.1.4.2.1.1
-- 1.3.6.1.4.1.25882.2.1.2.7.1.4.2.1.1
		-- 1.3.6.1.4.1.25882.2.1.2.7.1.4.2.1.1
		arraySectorTableIndex OBJECT-TYPE
			SYNTAX Integer32
			MAX-ACCESS read-only
			STATUS current
			DESCRIPTION
				"Table Index unrelated to Sector ID or antenna ID."
			::= { arraySectorConfigurationEntry 1 }

		
--   1.3.6.1.4.1.25882.2.1.2.7.1.4.2.1.2
-- 1.3.6.1.4.1.25882.2.1.2.7.1.4.2.1.2
		-- 1.3.6.1.4.1.25882.2.1.2.7.1.4.2.1.2
		arraySectorID OBJECT-TYPE
			SYNTAX Integer32
			MAX-ACCESS read-only
			STATUS current
			DESCRIPTION
				"Sector ID"
			::= { arraySectorConfigurationEntry 2 }

		
--   1.3.6.1.4.1.25882.2.1.2.7.1.5
-- 1.3.6.1.4.1.25882.2.1.2.7.1.5
		-- 1.3.6.1.4.1.25882.2.1.2.7.1.5
		arrayReporting OBJECT IDENTIFIER ::= { arrayObjects 5 }

		
--   1.3.6.1.4.1.25882.2.1.2.7.1.5.1
-- 1.3.6.1.4.1.25882.2.1.2.7.1.5.1
		-- 1.3.6.1.4.1.25882.2.1.2.7.1.5.1
		sectorReportingEnabled OBJECT-TYPE
			SYNTAX INTEGER
				{
				enabled(1),
				disabled(2)
				}
			MAX-ACCESS read-only
			STATUS current
			DESCRIPTION
				"Boolean indicating whether or not sector reports
				are enabled."
			::= { arrayReporting 1 }

		
--   1.3.6.1.4.1.25882.2.1.2.7.1.5.2
-- 1.3.6.1.4.1.25882.2.1.2.7.1.5.2
		-- 1.3.6.1.4.1.25882.2.1.2.7.1.5.2
		transitionReportingEnabled OBJECT-TYPE
			SYNTAX INTEGER
				{
				enabled(1),
				disabled(2)
				}
			MAX-ACCESS read-only
			STATUS current
			DESCRIPTION
				"Boolean indicating whether or not transition reports
				are enabled."
			::= { arrayReporting 2 }

		
--   1.3.6.1.4.1.25882.2.1.2.7.1.5.3
-- 1.3.6.1.4.1.25882.2.1.2.7.1.5.3
		-- 1.3.6.1.4.1.25882.2.1.2.7.1.5.3
		sectorReportEventCount OBJECT-TYPE
			SYNTAX Integer32
			MAX-ACCESS read-write
			STATUS current
			DESCRIPTION
				"This counter increments for each sector report issued."
			::= { arrayReporting 3 }

		
--   1.3.6.1.4.1.25882.2.1.2.7.1.5.4
-- 1.3.6.1.4.1.25882.2.1.2.7.1.5.4
		-- 1.3.6.1.4.1.25882.2.1.2.7.1.5.4
		transitionReportEventCount OBJECT-TYPE
			SYNTAX Integer32
			MAX-ACCESS read-write
			STATUS current
			DESCRIPTION
				"This counter increments for each transition report issued."
			::= { arrayReporting 4 }

		
--   1.3.6.1.4.1.25882.2.1.2.7.1.5.5
-- 1.3.6.1.4.1.25882.2.1.2.7.1.5.5
		-- 1.3.6.1.4.1.25882.2.1.2.7.1.5.5
		sectorReportTagCount OBJECT-TYPE
			SYNTAX Integer32
			MAX-ACCESS read-write
			STATUS current
			DESCRIPTION
				"This counter increments for each tag reported in 
				sector reports. A tag may be reported more than 
				once."
			::= { arrayReporting 5 }

		
--   1.3.6.1.4.1.25882.2.1.2.7.1.5.6
-- 1.3.6.1.4.1.25882.2.1.2.7.1.5.6
		-- 1.3.6.1.4.1.25882.2.1.2.7.1.5.6
		transitionReportTagCount OBJECT-TYPE
			SYNTAX Integer32
			MAX-ACCESS read-write
			STATUS current
			DESCRIPTION
				"This counter increments for each tag reported in 
				transition reports. A tag may be reported more than 
				once."
			::= { arrayReporting 6 }

		
	
	END

--
-- IMPINJ-R680-MIB.mib
--
